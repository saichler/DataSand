/*
 * Copyright (c) 2016 DataSand,Sharon Aicler and others.  All rights reserved.
 *
 * This program and the accompanying materials are made available under the
 * terms of the Eclipse Public License v1.0 which accompanies this distribution,
 * and is available at http://www.eclipse.org/legal/epl-v10.html
 */
module yang-parent {

    namespace "datasand:example";

    prefix yang-parent;

    contact
      "Sharon Aicler <saichler@gmail.com>";

    description
      "YANG parent example";

    revision "2016-01-01" {
      description
        "example yang parent model";
    }

    grouping grouping-example{
        description
            "example for grouping";

        leaf example-string {
            description
                "example-string";
            type string;
        }
        leaf example-long {
            type int64;
        }
    }

    container container-example {
        uses grouping-example;
        leaf example-int {
            type int32;
        }
    }

    list list-example {
        leaf name {
            type string;
        }
    }
}
