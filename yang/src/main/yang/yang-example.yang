/*
 * Copyright (c) 2016 DataSand,Sharon Aicler and others.  All rights reserved.
 *
 * This program and the accompanying materials are made available under the
 * terms of the Eclipse Public License v1.0 which accompanies this distribution,
 * and is available at http://www.eclipse.org/legal/epl-v10.html
 */
module yang-example {

    namespace "datasand:example";

    prefix yang-example;
    import yang-parent { prefix parent; revision-date 2016-01-01; }

    contact
      "Sharon Aicler <saichler@gmail.com>";

    description
      "YANG example";

    revision "2016-01-01" {
      description
        "example yang model";
    }

    list example-list {
        uses parent:example-grouping;
        leaf example-long{
            type int64;
        }
    }
}
